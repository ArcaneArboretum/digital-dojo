[DOCUMENT]
MID: 320c6900c8a84aafbff4174829c7c5da
TITLE: Low-Level Requirements
PREFIX: LLR-
OPTIONS:
  ENABLE_MID: True

[REQUIREMENT]
MID: 037469baedd14d89a8efca99385d1948
UID: LLR-1
TITLE: Initial low-level requirement
STATEMENT: >>>
The software shall print a hello world message.
<<<
RELATIONS:
- TYPE: Parent
  VALUE: HLR-1
